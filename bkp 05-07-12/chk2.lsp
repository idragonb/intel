(load "excel utilities.lsp")

(defun chk2 ()
  (setq dwgname (vl-registry-read "HKEY_CURRENT_USER\\Software\\ACT\\Intel-Standards-Checker" "Current drawing"))
  (putinexcel "thisdwg" dwgname)
  (if (> (blkcount "I1184sht" "ModelSpace") 0) ; check iof in modelspace - if yes - error
     (putinexcel "TitleInModel" "No")
     (putinexcel "TitleInModel" "Yes")
  )
  (setq count-in-paper (blkcount "I1184sht" "PaperSpace")) ; check if in paperspace and only 1 - or error
  (cond
    ((= count-in-paper 0) (putinexcel "TitleInPaper" "No"))
    ((> count-in-paper 0) (putinexcel "TitleInPaper" "Yes"))
    ((> count-in-paper 1) (putinexcel "UniqueTitle" "No"))
  )
  (if (= count-in-paper 1) (putinexcel "UniqueTitle" "Yes"))
  (if (= count-in-paper 1)
    (progn
      (setq obj (getblk "I1184sht" "PaperSpace")) ; if only once in paper - get obj
      (setq blkid (vlax-get-property obj 'ObjectID))
      (setq blklyr (vlax-get-property obj 'Layer))
      (putinexcel "chk2Layer" blklyr)
      
      (setq titleatts (getatts blkid "PaperSpace"))

      (putinexcel "OldNum" (nth 1 (assoc "OLD-NUM" titleatts)))
      (putinexcel "Fwr" (nth 1 (assoc "FWR" titleatts)))
      (putinexcel "Rev" (nth 1 (assoc "##__##" titleatts)))
      (putinexcel "PlotScale" (nth 1 (assoc "PLOTSCALE" titleatts)))
      (putinexcel "Scale" (nth 1 (assoc "SCALE" titleatts)))
      (putinexcel "Title4" (nth 1 (assoc "TITLE-4" titleatts)))
      (putinexcel "Title3" (nth 1 (assoc "TITLE-3" titleatts)))
      (putinexcel "Title2" (nth 1 (assoc "TITLE-2" titleatts)))
      (putinexcel "Title1" (nth 1 (assoc "TITLE-1" titleatts)))
      (putinexcel "File" (nth 1 (assoc "FILE" titleatts)))
      (putinexcel "DwgNum" (nth 1 (assoc "DWG#" titleatts)))
      (putinexcel "DwgDate" (nth 1 (assoc "DRW_DATE" titleatts)))
      (putinexcel "CheckDate" (nth 1 (assoc "CHK_DATE" titleatts)))
      (putinexcel "CrsDate" (nth 1 (assoc "CRS_DATE" titleatts)))
      (putinexcel "SafDate" (nth 1 (assoc "SAF_DATE" titleatts)))
      (putinexcel "PlaDate" (nth 1 (assoc "PLA_DATE" titleatts)))
      (putinexcel "EngDate" (nth 1 (assoc "ENG_DATE" titleatts)))
      (putinexcel "AppDate" (nth 1 (assoc "APP_DATE" titleatts)))
      (putinexcel "Drawn" (nth 1 (assoc "DRAWN" titleatts)))
      (putinexcel "Checked" (nth 1 (assoc "CHECKED" titleatts)))
      (putinexcel "CrossCheck" (nth 1 (assoc "CROSSCHECK" titleatts)))
      (putinexcel "Safety" (nth 1 (assoc "SAFETY" titleatts)))
      (putinexcel "Planning" (nth 1 (assoc "PLANNING" titleatts)))
      (putinexcel "Engineer" (nth 1 (assoc "ENGINEER" titleatts)))
      (putinexcel "Approved" (nth 1 (assoc "APPROVED" titleatts)))
      (putinexcel "EqtCode" (nth 1 (assoc "EQT_CODE" titleatts)))
    )
  )
  (setq result (getresult "chk2"))
  (if (= result "x")
    (copytab "chk2results" "chk2")
  )

)
  
  
(defun getatts (objectid space /  nn)
    (setq acadobj (vlax-get-acad-object))
  (setq docs (vlax-get-property acadobj 'Documents))
  (setq dwgname (vl-registry-read "HKEY_CURRENT_USER\\Software\\ACT\\Intel-Standards-Checker" "Current drawing"))
  (setq doc (vlax-invoke-method docs 'Item dwgname))
  (setq database (vlax-get-property doc space)) ; ModelSpace PaperSpace
  (setq count (vlax-get-property database 'Count))
  (setq nn 0)
  (setq return '())
  (while (< nn count)
    (setq obj (vlax-invoke-method database 'Item nn))
    (setq objid (vlax-get-property obj 'ObjectID))
    (if (= objid objectid)
       (progn
	 (setq ent (vlax-vla-object->ename obj))
	 (setq ent (entnext ent))
	 (setq entlist (entget ent))
	 (setq c0 (cdr (assoc 0 entlist)))
	 (while (/= c0 "SEQEND")
	   (setq atttag (cdr (assoc 2 entlist)))
	   (setq atttext (cdr (assoc 1 entlist)))
           (setq return (append return (list (list atttag atttext))))
	   (setq ent (entnext ent))
	   (setq entlist (entget ent))
	   (setq c0 (cdr (assoc 0 entlist)))
	 )
       )
    )
    (setq nn (1+ nn))
  )
  return
)
  
; (blkcount "I1184sht" "ModelSpace")
; (blkcount "I1184sht" "PaperSpace")

(defun getblk (blkname space /  nn)
    (setq acadobj (vlax-get-acad-object))
  (setq docs (vlax-get-property acadobj 'Documents))
  (setq dwgname (vl-registry-read "HKEY_CURRENT_USER\\Software\\ACT\\Intel-Standards-Checker" "Current drawing"))
  (setq doc (vlax-invoke-method docs 'Item dwgname))
  (setq database (vlax-get-property doc space)) ; ModelSpace PaperSpace
  (setq count (vlax-get-property database 'Count))
  (setq nn 0)
  (setq return 0)
  (while (< nn count)
    (setq obj (vlax-invoke-method database 'Item nn))
    (setq objtype (vlax-get-property obj 'ObjectName))
    (if (= objtype "AcDbBlockReference")
      (if (= (vlax-get-property obj 'Name) blkname)
	(setq return obj)
      )
    )
    (setq nn (1+ nn))
  )
  return
)

  
(defun blkcount (blkname space / nn)
  (setq acadobj (vlax-get-acad-object))
  (setq docs (vlax-get-property acadobj 'Documents))
  (setq dwgname (vl-registry-read "HKEY_CURRENT_USER\\Software\\ACT\\Intel-Standards-Checker" "Current drawing"))
  (setq doc (vlax-invoke-method docs 'Item dwgname))
  (setq database (vlax-get-property doc space)) ; ModelSpace PaperSpace
  (setq count (vlax-get-property database 'Count))
  (setq nn 0)
  (setq return 0)
  (while (< nn count)
    (setq obj (vlax-invoke-method database 'Item nn))
    (setq objtype (vlax-get-property obj 'ObjectName))
    (if (= objtype "AcDbBlockReference")
      (if (= (vlax-get-property obj 'Name) blkname)
	(setq return (1+ return))
      )
    )
    (setq nn (1+ nn))
  )
  return
)
