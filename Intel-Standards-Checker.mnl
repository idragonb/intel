(vl-load-com)
(setq instdirINTEL (vl-registry-read "HKEY_CURRENT_USER\\Software\\ACT\\Intel-Standards-Checker" "Install directory"))
(setq acadobj (vlax-get-acad-object))
(setq prefobj (vlax-get-property acadobj 'Preferences))
(setq fileprefs (vlax-get-property prefobj 'Files))
(setq supportpaths (vlax-get-property fileprefs 'SupportPath))
(setq supportpaths (strcat supportpaths ";" instdirINTEL))
(vlax-put-property fileprefs 'SupportPath supportpaths)
(load "Intel Standards Checker.lsp")
(if (setq installdoc (findfile (strcat instdirINTEL "\\install.dwg")))
   (progn
      (setq delcmd (strcat "erase " installdoc))
      (command "shell" delcmd)
   )
)
(setq installdirectoryINTEL (strcat instdirINTEL "\\"))
(princ "Intel Standards Checker ready...")
