(defun chk15 (/ retval)
   (setq retval "ok")
   (setq let1 (substr (getvar "dwgname") 1 1))
   (if (or (= let1 "G") (= let1 "R"))
      (setq retval "NA")
   )
   (if (or (= let1 "K") (= let1 "M"))
      (setq retval (check2lines))
   )
   retval
)


(defun check2lines (/ retval nn)
   (setq retval "ok")
   (setq ssset (ssget "X" '((2 . "IBLK_1"))))
   (if (not ssset)
      (setq ssset (ssadd))
   )
   (setq ssset2 (ssget "X" '((2 . "I1184sht"))))
   (if ssset2
      (setq ssset (ssadd (ssname ssset2 0) ssset))
   )
   (if (> (sslength ssset) 8)
      (progn
         (appendreport "-Too many revision lines. ")
         (setq retval "X")
      )
   )
   (if (and (< (sslength ssset) 7) (> (sslength ssset) 2))
      (progn
         (appendreport "-Not enough revision lines. ")
         (setq retval "X")
      )
   )
   (setq nn 0)
   (setq thisretval "X")
   (while (< nn 7) 
      (setq ent (ssname ssset nn))
      (if ent
         (progn
            (setq entlist (entget ent))
            (setq c0 (cdr (assoc 0 entlist)))
         )
         (setq c0 "SEQEND")
      )
      (while (/= c0 "SEQEND")
         (setq ent (entnext ent))
         (setq entlist (entget ent))
         (setq c0 (cdr (assoc 0 entlist)))
         (if (/= c0 "SEQEND")
            (progn
               (setq c1 (cdr (assoc 1 entlist)))
               (setq c2 (cdr (assoc 2 entlist)))
               (if (or
                      (and (= c2 "R1DESC") (= c1 "RECORD DRAWING"))
                      (and (= c2 "R2DESC") (= c1 "RECORD DRAWING"))
                   )
                  (setq thisretval "ok")
               )
            )
          )
       )
      (setq nn (1+ nn))
   )
   (if (not (= thisretval "ok"))
      (progn
         (setq retval "X")
         (appendreport "-Revision lines incorrect. ")
      )
   )
   retval
)
