(defun chk18 (/ retval)
   (setq retval "ok")
   (setq tbllen-blk (gettbllen "BLOCK"))
   (setq tbllen-lyr (gettbllen "LAYER"))
   (setq tbllen-dms (gettbllen "DIMSTYLE"))
   (setq tbllen-stl (gettbllen "STYLE"))
   (setq tbllen-ltp (gettbllen "LTYPE"))
   (command "-layer" "set" "0" "")
   (command "-purge" "a" "*" "n")
   (if (or
          (/= tbllen-blk (gettbllen "BLOCK"))
          (/= tbllen-lyr (gettbllen "LAYER"))
          (/= tbllen-dms (gettbllen "DIMSTYLE"))
          (/= tbllen-stl (gettbllen "STYLE"))
          (/= tbllen-ltp (gettbllen "LTYPE"))
       )
      (setq retval "X")
   )
   retval
)

(defun gettbllen (tbltype / nn)
   (setq nn 0)
   (setq first T)
   (while (tblnext tbltype first)
      (setq first nil)
      (setq nn (1+ nn))
   )
   nn
)
